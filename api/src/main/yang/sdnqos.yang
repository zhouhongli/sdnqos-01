module sdnqos {
    yang-version 1;
    namespace "urn:opendaylight:params:xml:ns:yang:sdnqos";
    prefix "sdnqos";

    revision "2015-01-05" {
        description "Initial revision of sdnqos model";
    }    
}
